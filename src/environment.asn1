MECViewEnvironmentModule DEFINITIONS AUTOMATIC TAGS ::=
BEGIN
 
IMPORTS
    ReferencePoint, PositionOffset, MovingVector, ObjectType, ObjectSize, Header
FROM MECViewGeneralModule;

Covariance ::= SEQUENCE {
    north-pos-east-pos  INTEGER (-225000000..225000000) OPTIONAL,
    north-pos-north-vel INTEGER (-9000000..9000000) OPTIONAL,
    north-pos-east-vel  INTEGER (-9000000..9000000) OPTIONAL,
    east-pos-north-vel  INTEGER (-9000000..9000000) OPTIONAL,
    east-pos-east-vel   INTEGER (-9000000..9000000) OPTIONAL,
    north-vel-east-vel  INTEGER (-360000..360000) OPTIONAL
}

PathPoint ::= SEQUENCE {
    position-offset	PositionOffset,
    probability		INTEGER (0..200)
}

Path ::= SEQUENCE OF PathPoint

PredictedPath ::= SEQUENCE {
    timestamp-dt	INTEGER (0..500),
    path		Path
}

SectorIds ::= SEQUENCE OF INTEGER(0..255)

Error ::= SEQUENCE {
	id		INTEGER (0..255),
	sector-ids	SectorIds
}
 
Errors ::= SEQUENCE OF Error

EnvironmentEnvelope ::= SEQUENCE {
    version            INTEGER (0..MAX),
    server-id	       INTEGER (0..MAX),
    reference-point    ReferencePoint,
	error-codes		   Errors
}

EnvironmentObjectDetection ::= SEQUENCE {
    timestamp    				INTEGER (0..1209600000),
    measured					BOOLEAN,
    global-id					INTEGER (0..MAX),
    probability-of-existence    INTEGER (0..200),
    position-offset             PositionOffset,
    moving-vector               MovingVector OPTIONAL,
    type                        ObjectType,
    type-probability            INTEGER (0..200),
    size                        ObjectSize,
    covariance					Covariance,
    orientation                 INTEGER (0..3600),
    std-dev-orientation         INTEGER (0..1800),
    predicted-path				PredictedPath
}

EnvironmentObjectDetections ::= SEQUENCE OF EnvironmentObjectDetection

EnvironmentFrame ::= SEQUENCE {
    header              Header,
    envelope            EnvironmentEnvelope,
    object-detections   EnvironmentObjectDetections
}

Area ::= SEQUENCE OF ReferencePoint

Sector ::= SEQUENCE {
	id 			INTEGER (0..255),
	area		Area
}

Sectors ::= SEQUENCE OF Sector

InitMessage ::= SEQUENCE {
	header			Header,
	envelope		EnvironmentEnvelope,
	sectors			Sectors
}

END
